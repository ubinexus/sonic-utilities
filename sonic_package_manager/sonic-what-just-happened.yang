module sonic-what-just-happened {

    yang-version 1.1;

	namespace "http://github.com/Azure/sonic-what-just-happened";
	prefix what-just-happened;

	description "What-Just-Happened yang Module for SONiC OS";

	revision 2020-05-01 {
		description "First Revision";
	}

	container sonic-what-just-happened {

		container WJH_CHANNEL {

			description "What-Just-Happened channels configuration";

			list WJH_CHANNEL_LIST {

				description "List of What-Just-Happened channels";

				key "name";

				leaf name {
					type string {
                        pattern "l1|forwarding|buffer";
                    }
				}

				leaf "type" {
					type string {
						pattern "raw|aggregated|raw_and_aggregated";
					}
				}

                leaf drop_category_list {
                    type string;
                }
			}
			/* end of WJH_CHANNEL_LIST */
		}
		/* end of WJH_CHANNEL container */

		container WJH {

			description "What-Just-Happened global configuration";

            container global {

                leaf mode {
                    type string {
                        pattern "debug";
                    }
                    default "debug";
                }

                leaf nice_level {
                    type int {
                        range -20..19;
                    }
                    default 1;
                }

                leaf pci_bandwidth {
                    type int {
                        range 0..100;
                    }
                    default 50;
                }

            }
		}
		/* end of container WJH */
	}
    /* end of container sonic-what-just-happened */
}
/* end of module sonic-what-just-happened */
